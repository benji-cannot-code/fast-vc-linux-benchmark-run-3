FASTVC-BENCH-CORPUS:linux-main-100k-v1-e0bd41dc-8e12-4f1b-978d-a3645ae59da0
RsaPrivKey ::= SEQUENCE {
	version		INTEGER,
	n		INTEGER ({ qat_rsa_get_n }),
	e		INTEGER ({ qat_rsa_get_e }),
	d		INTEGER ({ qat_rsa_get_d }),
	prime1		INTEGER,
	prime2		INTEGER,
	exponent1	INTEGER,
	exponent2	INTEGER,
	coefficient	INTEGER
}
