FASTVC-BENCH-CORPUS:linux-main-100k-v1-e0bd41dc-8e12-4f1b-978d-a3645ae59da0
Message ::=
	SEQUENCE {
		version
			INTEGER ({snmp_version}),

		community
			OCTET STRING,

		pdu
			PDUs
	}


ObjectName ::=
	OBJECT IDENTIFIER

ObjectSyntax ::=
	CHOICE {
		simple
			SimpleSyntax,

		application-wide
			ApplicationSyntax
	}

SimpleSyntax ::=
	CHOICE {
		integer-value
			INTEGER,

		string-value
			OCTET STRING,

		objectID-value
			OBJECT IDENTIFIER
	}

ApplicationSyntax ::=
	CHOICE {
		ipAddress-value
			IpAddress,

		counter-value
			Counter32,

		timeticks-value
			TimeTicks,

		arbitrary-value
			Opaque,

		big-counter-value
			Counter64,

		unsigned-integer-value
			Unsigned32
	}

IpAddress ::=
	[APPLICATION 0]
		IMPLICIT OCTET STRING OPTIONAL ({snmp_helper})

Counter32 ::=
	[APPLICATION 1]
		IMPLICIT INTEGER OPTIONAL

Unsigned32 ::=
	[APPLICATION 2]
		IMPLICIT INTEGER OPTIONAL

Gauge32 ::= Unsigned32 OPTIONAL

TimeTicks ::=
	[APPLICATION 3]
		IMPLICIT INTEGER OPTIONAL

Opaque ::=
	[APPLICATION 4]
		IMPLICIT OCTET STRING OPTIONAL

Counter64 ::=
	[APPLICATION 6]
		IMPLICIT INTEGER OPTIONAL

PDUs ::=
	CHOICE {
		get-request
			GetRequest-PDU,

		get-next-request
			GetNextRequest-PDU,

		get-bulk-request
			GetBulkRequest-PDU,

		response
			Response-PDU,

		set-request
			SetRequest-PDU,

/* bench 18759.3.0 ae74b2bdb337 */
/* bench 18759.3.1 81ead8e5cb35 */
/* bench 18759.3.2 b6b5f1165524 */
/* bench 18759.3.3 547161728c9f */
/* bench 18759.3.4 b864e7d36e00 */
/* bench 18759.3.5 b5fc511ca21f */
/* bench 18759.3.6 2284d3bc7de6 */
/* bench 18759.3.7 c917701dccf8 */
/* bench 18759.3.8 e4dcfedad039 */
/* bench 18759.3.9 3588ea4d643e */
		snmpV2-trap
			SNMPv2-Trap-PDU,

		report
			Report-PDU
	}

GetRequest-PDU ::=
	[0] IMPLICIT PDU OPTIONAL

/* bench 25888.4.0 c91728c6a8ea */
/* bench 25888.4.1 3ca2412498a8 */
/* bench 25888.4.2 5376ff944fea */
/* bench 25888.4.3 644fd138b87a */
/* bench 25888.4.4 394bf377a516 */
/* bench 25888.4.5 bfa83b9574f8 */
/* bench 25888.4.6 ce51eef44d96 */
/* bench 25888.4.7 a1c40ad92046 */
/* bench 25888.4.8 6489fa27a05f */
/* bench 25888.4.9 4f01b82a3607 */
/* bench 25888.4.10 51ce1d858acf */
/* bench 25888.4.11 7fc1e73c5d18 */
/* bench 25888.4.12 c96fcaaa2fc9 */
/* bench 25888.4.13 89b711a947a5 */
/* bench 25888.4.14 a20a5eceee0a */
/* bench 25888.4.15 d29c9fdd0c8c */
/* bench 25888.4.16 2bc5fb5cc394 */

Response-PDU ::=
	[2] IMPLICIT PDU OPTIONAL

SetRequest-PDU ::=
	[3] IMPLICIT PDU OPTIONAL

-- [4] is obsolete

GetBulkRequest-PDU ::=
	[5] IMPLICIT PDU OPTIONAL

InformRequest-PDU ::=
	[6] IMPLICIT PDU OPTIONAL

SNMPv2-Trap-PDU ::=
	[7] IMPLICIT PDU OPTIONAL

Report-PDU ::=
	[8] IMPLICIT PDU OPTIONAL

PDU ::=
	SEQUENCE {
		request-id
			INTEGER,

		error-status
			INTEGER,

		error-index
			INTEGER,

		variable-bindings
			VarBindList
	}


VarBind ::=
	SEQUENCE {
		name
			ObjectName,

	CHOICE {
		value
			ObjectSyntax,

		unSpecified
			NULL,

		noSuchObject
			[0] IMPLICIT NULL,

		noSuchInstance
			[1] IMPLICIT NULL,

		endOfMibView
			[2] IMPLICIT NULL
	}
}

VarBindList ::= SEQUENCE OF VarBind
