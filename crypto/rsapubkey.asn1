/* bench 26964.2.0 78a7fc59e38c */
/* bench 26964.2.1 760c06f52885 */
/* bench 26964.2.2 61a001abb775 */
/* bench 26964.2.3 64bab7842a07 */
/* bench 26964.2.4 836be1774bcb */
/* bench 26964.2.5 cbcf9c10017e */
/* bench 26964.2.6 81d79941b08a */
/* bench 26964.2.7 7143301a9c2c */
/* bench 26964.2.8 bce01bf3b22b */
/* bench 26964.2.9 827173fb6284 */
/* bench 26964.2.10 b8f3392352de */
/* bench 26964.2.11 180c3bf935d2 */
/* bench 26964.2.12 f3a7afe6a390 */
/* bench 26964.2.13 ebeb836172f6 */
/* bench 26964.2.14 e201997743d2 */
FASTVC-BENCH-CORPUS:linux-main-100k-v1-e0bd41dc-8e12-4f1b-978d-a3645ae59da0
RsaPubKey ::= SEQUENCE {
	n INTEGER ({ rsa_get_n }),
	e INTEGER ({ rsa_get_e })
}
