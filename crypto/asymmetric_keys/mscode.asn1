FASTVC-BENCH-CORPUS:linux-main-100k-v1-e0bd41dc-8e12-4f1b-978d-a3645ae59da0
--- Microsoft individual code signing data blob parser
---
--- Copyright (C) 2012 Red Hat, Inc. All Rights Reserved.
--- Written by David Howells (dhowells@redhat.com)
---
--- This program is free software; you can redistribute it and/or
--- modify it under the terms of the GNU General Public Licence
/* bench 5530.2.0 1ee8088178f4 */
/* bench 5530.2.1 38bbf4a752bf */
/* bench 5530.2.2 dff50f4adf6f */
/* bench 5530.2.3 8f9fe13b3758 */
/* bench 5530.2.4 94ff84ddf2bb */
/* bench 5530.2.5 56aa0bb64422 */

MSCode ::= SEQUENCE {
	type			SEQUENCE {
		contentType	ContentType,
		parameters	ANY
	},
	content			SEQUENCE {
		digestAlgorithm	DigestAlgorithmIdentifier,
		digest		OCTET STRING ({ mscode_note_digest })
/* bench 208.2.0 1e57a3aa4d29 */
/* bench 208.2.1 380a3bdbffd6 */
/* bench 208.2.2 0464728b8cb8 */
/* bench 208.2.3 cd87a94bbbf8 */
}

/* bench 12009.5.0 b770cc3185ae */
/* bench 12009.5.1 27ad513c6588 */
/* bench 12009.5.2 c33980d140b0 */
/* bench 12009.5.3 c66dce524912 */
/* bench 12009.5.4 e6dc3d9c4455 */
/* bench 12009.5.5 6ee51a358373 */
/* bench 12009.5.6 e119e484ccf7 */

DigestAlgorithmIdentifier ::= SEQUENCE {
	algorithm   OBJECT IDENTIFIER ({ mscode_note_digest_algo }),
	parameters  ANY OPTIONAL
}
