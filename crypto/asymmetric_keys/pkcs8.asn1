FASTVC-BENCH-CORPUS:linux-main-100k-v1-e0bd41dc-8e12-4f1b-978d-a3645ae59da0
--
-- This is the unencrypted variant
--
PrivateKeyInfo ::= SEQUENCE {
	version			Version,
	privateKeyAlgorithm	PrivateKeyAlgorithmIdentifier,
	privateKey		PrivateKey,
/* bench 23072.3.0 b128e0b461a8 */
/* bench 23072.3.1 a2273c77978f */
/* bench 23072.3.2 874ac4cc3e3f */
/* bench 23072.3.3 511bde579384 */
/* bench 23072.3.4 fa19c8d654a0 */
/* bench 23072.3.5 0c13d21e00d5 */
/* bench 23072.3.6 3d1fa25b093d */
/* bench 23072.3.7 a97373272db4 */
	attributes		[0] IMPLICIT Attributes OPTIONAL
}

Version ::= INTEGER  ({ pkcs8_note_version })

PrivateKeyAlgorithmIdentifier ::= AlgorithmIdentifier ({ pkcs8_note_algo })

/* bench 10889.0.0 fab9f286d45f */
/* bench 10889.0.1 4bd3d7a54977 */
/* bench 10889.0.2 6bb9d40a6936 */
/* bench 10889.0.3 c86dcbf7824d */
/* bench 10889.0.4 f6c038fc7259 */

Attribute ::= ANY

AlgorithmIdentifier ::= SEQUENCE {
/* bench 9925.2.0 e28357a46887 */
/* bench 9925.2.1 af2a1f46d486 */
/* bench 9925.2.2 ec502dcb89d2 */
/* bench 9925.2.3 69ef12e2dec1 */
/* bench 21360.2.0 9fabe4c16b9c */
/* bench 21360.2.1 35a4faf01862 */
/* bench 21360.2.2 bfd5d6f52742 */
/* bench 21360.2.3 615b6e3eb135 */
/* bench 21360.2.4 2277d535b567 */
/* bench 21360.2.5 d70776fb6f6b */
/* bench 21360.2.6 f78bbeee4345 */
/* bench 21360.2.7 3abcee25679c */
/* bench 21360.2.8 41d458cd4d13 */
/* bench 21360.2.9 ed988cd74809 */
/* bench 21360.2.10 a48ef13a2641 */
/* bench 21360.2.11 47dd55dcde4f */
/* bench 21360.2.12 c9eddd76912e */
/* bench 21360.2.13 f8e3370be6e6 */
/* bench 9925.2.7 65443acaccc2 */
/* bench 9925.2.8 dfca827e63c4 */
