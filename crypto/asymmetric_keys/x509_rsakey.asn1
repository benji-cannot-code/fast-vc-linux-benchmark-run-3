FASTVC-BENCH-CORPUS:linux-main-100k-v1-e0bd41dc-8e12-4f1b-978d-a3645ae59da0
RSAPublicKey ::= SEQUENCE {
	modulus			INTEGER ({ rsa_extract_mpi }),	-- n
	publicExponent		INTEGER ({ rsa_extract_mpi })	-- e
	}
