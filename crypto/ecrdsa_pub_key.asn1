FASTVC-BENCH-CORPUS:linux-main-100k-v1-e0bd41dc-8e12-4f1b-978d-a3645ae59da0
EcrdsaPubKey ::= OCTET STRING ({ ecrdsa_parse_pub_key })
/* bench 9016.2.0 7f1772f9a0c7 */
/* bench 9016.2.1 62370581c157 */
/* bench 9016.2.2 c98be5763b50 */
/* bench 9016.2.3 00fa658222ab */
/* bench 9016.2.4 43a3f287c5bc */
/* bench 9016.2.5 330286db1c78 */
/* bench 9016.2.6 08b99d040916 */
/* bench 9016.2.7 1296302cb605 */
/* bench 9016.2.8 4394d3fa73a5 */
/* bench 9016.2.9 83d2b1169be1 */
/* bench 9016.2.10 bf8c2bb09989 */
/* bench 9016.2.11 d34ea8c64ee5 */
/* bench 9016.2.12 5e05b315c2e4 */
/* bench 7902.4.1 2886d275bd05 */
