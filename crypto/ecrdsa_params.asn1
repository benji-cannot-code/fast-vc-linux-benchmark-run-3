FASTVC-BENCH-CORPUS:linux-main-100k-v1-e0bd41dc-8e12-4f1b-978d-a3645ae59da0
EcrdsaParams ::= SEQUENCE {
	curve	OBJECT IDENTIFIER ({ ecrdsa_param_curve }),
	digest	OBJECT IDENTIFIER OPTIONAL ({ ecrdsa_param_digest })
}
/* bench 7208.0.0 95e752ca0a5f */
/* bench 7208.0.1 b3c9d801f6ce */
/* bench 7208.0.2 8d02c9807d79 */
/* bench 7208.0.3 bda3aa197ecc */
/* bench 7208.0.4 a402179d7b38 */
/* bench 7208.0.5 09f8d8792c16 */
/* bench 7208.0.6 a4b324c74fb2 */
/* bench 7208.0.7 d81667192858 */
