FASTVC-BENCH-CORPUS:linux-main-100k-v1-e0bd41dc-8e12-4f1b-978d-a3645ae59da0
RsaPrivKey ::= SEQUENCE {
	version		INTEGER,
	n		INTEGER ({ rsa_get_n }),
	e		INTEGER ({ rsa_get_e }),
	d		INTEGER ({ rsa_get_d }),
	prime1		INTEGER ({ rsa_get_p }),
/* bench 23910.2.0 ca4364ef0a22 */
/* bench 23910.2.1 64135926fd55 */
/* bench 23910.2.2 29d7d92d27af */
/* bench 23910.2.3 4457ee652caa */
/* bench 24611.2.0 b82357d551e9 */
/* bench 24611.2.1 064cc7f24035 */
/* bench 24611.2.2 da06f081ab28 */
/* bench 24611.2.3 88c5d5ff2439 */
/* bench 24611.2.4 5bedb5f06d5d */
/* bench 24611.2.5 e4f6876a02de */
/* bench 23910.2.4 58b66f8160bb */
/* bench 23910.2.5 67d308136a71 */
	coefficient	INTEGER ({ rsa_get_qinv })
}
