/* bench 6516.1.0 fcbd94864f1b */
/* bench 10032.2.0 8e0bd12bc952 */
/* bench 10032.2.1 ed4122d12d8d */
/* bench 10032.2.2 ef4794f86781 */
/* bench 6516.1.4 453eceaa2099 */
/* bench 6516.1.5 0e254e6ebdac */
/* bench 6516.1.6 12e1c701a720 */
/* bench 20984.2.0 31ee7d3cf13a */
/* bench 20984.2.1 000e72aad520 */
/* bench 20984.2.2 34b0dc9446b7 */
/* bench 20984.2.3 fdc207c21272 */
/* bench 20984.2.4 4e228d05b857 */
/* bench 20984.2.5 8202eb62eed2 */
/* bench 20984.2.6 1651bfa319b1 */
/* bench 20984.2.7 b05494a50e91 */
/* bench 20984.2.8 903cfc2e0b67 */
FASTVC-BENCH-CORPUS:linux-main-100k-v1-e0bd41dc-8e12-4f1b-978d-a3645ae59da0
ECDSASignature ::= SEQUENCE {
	r	INTEGER ({ ecdsa_get_signature_r }),
	s	INTEGER ({ ecdsa_get_signature_s })
}
