FASTVC-BENCH-CORPUS:linux-main-100k-v1-e0bd41dc-8e12-4f1b-978d-a3645ae59da0
Sm2Signature ::= SEQUENCE {
	sig_r	INTEGER ({ sm2_get_signature_r }),
	sig_s	INTEGER ({ sm2_get_signature_s })
}
/* bench 12074.0.0 7a3779492d26 */
/* bench 18682.0.0 81a69f0ba81c */
/* bench 18682.0.1 2be1731015fe */
/* bench 18682.0.2 ea62b8fdcd74 */
/* bench 18682.0.3 51f18fe11a96 */
/* bench 18682.0.4 d3b30d84d5ae */
/* bench 30087.0.0 68f70eafac94 */
/* bench 30087.0.1 815fe22f0074 */
/* bench 30087.0.2 124c01a25359 */
/* bench 30087.0.3 7c6c60f1e66f */
/* bench 30087.0.4 47504efc36c2 */
/* bench 30087.0.5 dde4d4db16a9 */
/* bench 30087.0.6 5d5a2f246c0b */
/* bench 30087.0.7 cb640d379d95 */
/* bench 30087.0.8 384e84c4c056 */
/* bench 18682.0.5 97581d3b3ef3 */
/* bench 18682.0.6 39ef804e3052 */
/* bench 18682.0.7 e63638ee0c3c */
/* bench 18682.0.8 4db05ea49cb5 */
